RiftExtension DEFINITIONS ::=
BEGIN

IMPORTS
    Extension
        FROM PKIX1Explicit88 { iso(1) identified-organization(3) dod(6) internet(1) security(5) mechanisms(5) pkix(7) id-mod(0) id-pkix1-explicit(18) };

id-rift-ed25519-identity OBJECT IDENTIFIER ::= { joint-iso-itu-t(2) uuid(25) 293029629918709742181702189012786017422 }

RiftEd25519PublicKey ::= OCTET STRING (SIZE (32))

END
